FME workspace etjanst_gransmarkering.fmw

Parameters:
- email = id[137667]   # " " Email body

Creator
    GEOMTYPE = Geometry Object
    NUM = 1
    CREATED -> StringSearcher
Junction
    -> AttributeCreator_2

Bookmark: Get open e information
StringSearcher
    CASE = no
    MATCHED_RESULT_ATTR = _case
    REGEXP = (?<=id\[)\d+
    STRING_TO_SEARCH = $(email)
    MATCHED -> HTTPCaller
HTTPCaller
    AUTH_METHOD = Web Connection
    AUTH_NAMED_CONNECTION = API User
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = Https://minasidor-api.trollhattan.se:8443/api/instanceapi/getinstance/@Value(_case)/xml
    TRANSFER_TIMEOUT_LENGTH = 90
    USE_COOKIES = No
    VERIFY_SSL_CERTIFICATES = Yes
    -> XMLFragmenter
XMLFragmenter
    ATTRIBUTE_XML = _response_body
    EMBEDDED_EXPRESSIONS = FlowInstance
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    IGNORE_DATASET_EXTERNAL_DTD = No
    MERGE_ATTRS = Yes
    REJECT_FEATURES_WITH_NO_FRAGMENTS = YES
    XML_SOURCE_TYPE = Attribute with XML document
    FRAGMENTS -> AttributeExposer
AttributeExposer
    ATTR_LIST = Values.bild_ovanifran.File.Name,Values.bild_ovanifran.File.EncodedData,Values.mailadress.mailadress,Values.visa_plats_karta.EPSG,Values.visa_plats_karta.Geometries.Geometry.WKT
    -> TextDecoder

Bookmark: jpeg information
TextDecoder
    ATTR_ENCODING = fme-binary
    DEST_ATTR = _decoded
    ENCODING_TYPE = Base64
    STRING_TO_DECODE = @Value(Values.bild_ovanifran.File.EncodedData)
    -> AttributeFileWriter
AttributeFileWriter
    CHAR_ENCODING = fme-binary
    FILE_NAME = $(FME_SHAREDRESOURCE_TEMP)/FME120/@Value(Values.bild_ovanifran.File.Name)
    OVERWRITE_FILE = Overwrite file
    SOURCE_ATTR = _decoded
    -> AttributeKeeper
    <REJECTED> -> Junction
AttributeKeeper
    CREATE_BULK_MODE_FEATURES = NO
    KEEP_ATTRS = Values.bild_ovanifran.File.Name,_case,Values.mailadress.mailadress,Values.visa_plats_karta.EPSG,Values.visa_plats_karta.Geometries.Geometry.WKT
    -> FeatureReader [INITIATOR]
FeatureReader
    ATTR_ACCUM_MODE = Merge Initiator and Result
    ATTR_CONFLICT_RES = Use Result
    ATTR_IGNORE_NULLS = No
    COMBINE_GEOM = Use Result
    DATASET = $(FME_SHAREDRESOURCE_TEMP)/FME120/@Value(Values.bild_ovanifran.File.Name)
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_FORMAT_RATIONAL_AS_FRACTION = No
    JPEG_GROUP_BY_DATASET = No
    JPEG_READER_META_ATTRIBUTES = fme_dataset fme_basename
    JPEG_USE_SEARCH_ENVELOPE = NO
    OUTPUT_FEATURES_DISPLAY = Schema and Data Features
    <OTHER> -> AttributeExposer_2
    <REJECTED> -> AttributeCreator_2
AttributeExposer_2
    ATTR_LIST = jpeg_exif_gpsaltitude,jpeg_exif_gpslongitude,jpeg_exif_gpslatitude,jpeg_exif_datetime
    -> TestFilter
    -> FileDeleter_2

Bookmark: Action
TestFilter
    DEFAULT_VALUE = <UNFILTERED>
    PASSED_TEST_GROUP_OUTPUT = FIRST
    TEST_LIST:
      "BOOL_OP,AND,COMPOSITE_TEST,""""""1 AND 2"""""",TEST_CLAUSE,TEST jpeg_exif_gpslatitude ATTRIBUTE_HAS_A_VALUE ""
      TEST jpeg_exif_gpslongitude ATTRIBUTE_HAS_A_VALUE """,Geo,"BOOL_OP,OR,COMPOSITE_TEST,""""""1"""""",TEST_CLAUSE,TEST Values.visa_plats_karta.Geometries.Geometry.WKT ATTRIBUTE_HAS_A_VALUE """,Kartnal
    Geo -> AttributeCreator
    Kartnal -> AttributeCreator_4
    <UNFILTERED> -> AttributeCreator_2
Note: Meddelande mejl
AttributeCreator
    ATTR_TABLE:
      SET_TO _opene.status = Kartredovisad
      SET_TO _email.subject = Fastighetsgränser – Fotografera gränsmarkeringar Ärende nr @Value(_case)
      SET_TO _email.message = <p>Tack för ditt bidrag!
        <br>
        <br>
        Du kan se resultatet på <a href="https://kartportalen.trollhattan.se/spatialmap?page=minimap2.showmap&id=bb651081-ff85-4138-8956-25e914358829&version=2.13">Trollhättans externa kartportal (Trollhattan.se).</a>
        <br>
        Vi jobbar kontinuerligt med att mäta in gränsmarkeringar och ditt bidrag underlättar detta arbete.</p>
      SET_TO typ = Bild
    -> HTTPCaller_2
    -> AttributeTrimmer
Note: Meddelande mejl
AttributeCreator_4
    ATTR_TABLE:
      SET_TO _opene.status = Kartredovisad
      SET_TO _email.subject = Fastighetsgränser – Fotografera gränsmarkeringar Ärende nr @Value(_case)
      SET_TO _email.message = <p>Tack för ditt bidrag!
        <br>
        <br>
        Du kan se resultatet på <a href="https://kartportalen.trollhattan.se/spatialmap?page=minimap2.showmap&id=bb651081-ff85-4138-8956-25e914358829&version=2.13">Trollhättans externa kartportal (Trollhattan.se).</a>
        <br>
        Vi jobbar kontinuerligt med att mäta in gränsmarkeringar och ditt bidrag underlättar detta arbete.</p>
      SET_TO typ = Kartnål
    -> HTTPCaller_2
    -> GeometryReplacer
Note: Meddelande mejl - ej koord
AttributeCreator_2
    ATTR_TABLE:
      SET_TO _opene.status = Avslutad
      SET_TO _email.subject = Fastighetsgränser – Fotografera gränsmarkeringar Ärende nr @Value(_case)
      SET_TO _email.message = <p>Oj, något gick fel!
        <br>
        <br>
        Det verkar som att du inte har satt ut någon nål i kartan.
        Har du möjlighet, så skicka gärna in ett nytt ärende för gränsmarkeringen.
        <br>
        <br>
        Ärende nr. @Value(_case), har slutförts.</p>
    -> HTTPCaller_2

Bookmark: Coord from jpg
AttributeTrimmer
    SRC_ATTRS = jpeg_exif_gpslatitude,jpeg_exif_gpslongitude
    TRIM_CHARS = ()
    TRIM_TO_NONE = Yes
    TRIM_TYPE = Both
    -> AttributeSplitter_2

Bookmark: Longitude decimal degrees
AttributeSplitter_2
    ATTR_NAME = jpeg_exif_gpslongitude
    DELIMITER = " "
    DROP_EMPTY_PARTS = No
    LIST_NAME = _long
    TRIM_OPTION = Both
    -> DecimalDegreesCalculator_2
DecimalDegreesCalculator_2
    DEGREES = _long{0}
    DEST_ATTR = longitude
    MINUTES = _long{1}
    SECONDS = _long{2}
    -> AttributeSplitter

Bookmark: Latitude decimal degrees
AttributeSplitter
    ATTR_NAME = jpeg_exif_gpslatitude
    DELIMITER = " "
    DROP_EMPTY_PARTS = No
    LIST_NAME = _lat
    TRIM_OPTION = Both
    -> DecimalDegreesCalculator
DecimalDegreesCalculator
    DEGREES = _lat{0}
    DEST_ATTR = latitude
    MINUTES = _lat{1}
    SECONDS = _lat{2}
    -> VertexCreator

Bookmark: Create point
Note: Latitude - Y - north / Longitude - X - east
VertexCreator
    MEASURE_TYPE = Continuous
    MODE_NAME = Replace with Point
    XVAL = @Value(longitude)
    YVAL = @Value(latitude)
    -> Reprojector
Reprojector
    DEST = EPSG:3007
    INTERPOLATION_TYPE_NAME = Nearest Neighbor
    RASTER_CELL_SIZE = Preserve Cells
    RASTER_TOLERANCE = 0.0
    SOURCE = LL84
    REPROJECTED -> CoordinateSystemSetter
CoordinateSystemSetter
    COORDSYS = EPSG:3007
    -> DateTimeConverter

Bookmark: Write to database
DateTimeConverter
    DATETIME_ATTR = jpeg_exif_datetime
    IN_FORMAT = %Y:%m:%d %H:%M:%S$
    OUT_FORMAT = %Y-%m-%d
    PASSTHROUGH = NO
    REPAIR_INPUT = YES
    -> AttributeManager
AttributeManager
    ATTR_TABLE:
      RENAME_SET_VALUE _opene.status > STATUS
      REMOVE _email.subject
      REMOVE _email.message
      RENAME_SET_VALUE _case > ARENDENR
      REMOVE Values.bild_ovanifran.File.Name
      REMOVE jpeg_exif_gpsaltitude
      REMOVE jpeg_exif_gpslongitude
      SET_TO EAST = @XValue()
      SET_TO NORTH = @YValue()
      RENAME_SET_VALUE jpeg_exif_datetime > FOTO_DATUM
      SET_TO UUID = @UUID()
      SET_TO ID_NR
      RENAME_SET_VALUE typ > TYP
    -> FeatureWriter [Output]
FeatureWriter
    DATASET = Karta
    DATASET_ATTR = _dataset
    FEATURE_TYPE_LIST_ATTR = _feature_type
    FORMAT = MSSQL_SPATIAL
    MSSQL_SPATIAL_BULK_INSERT = YES
    MSSQL_SPATIAL_COMMAND_TIMEOUT = 30
    MSSQL_SPATIAL_COORDINATE_SYSTEM_GRANULARITY = FEATURE_TYPE
    MSSQL_SPATIAL_HANDLE_MULTIPLE_SPATIAL_COLUMNS = NO
    MSSQL_SPATIAL_NAMED_CONNECTION = Karta
    MSSQL_SPATIAL_ORIENT_POLYGONS = YES
    MSSQL_SPATIAL_SPATIAL_COLUMN = GEOM
    MSSQL_SPATIAL_SPATIAL_TYPE = geometry
    MSSQL_SPATIAL_START_TRANSACTION = 0
    MSSQL_SPATIAL_TRANSACTION_INTERVAL = 500
    TOTAL_FEATURES_WRITTEN_ATTR = _total_features_written

Bookmark: Create point
GeometryReplacer
    KIND_LONG = OGC Well Known Text
    OGC_WKT_PRECISION_DISPLAY = 64-bit
    REMOVE_ATTRIBUTE = No
    SOURCE = @Value(Values.visa_plats_karta.Geometries.Geometry.WKT)
    -> Reprojector_2
Reprojector_2
    DEST = EPSG:3007
    INTERPOLATION_TYPE_NAME = Nearest Neighbor
    RASTER_CELL_SIZE = Preserve Cells
    RASTER_TOLERANCE = 0.0
    SOURCE = EPSG:3006
    REPROJECTED -> CoordinateSystemSetter_2
CoordinateSystemSetter_2
    COORDSYS = EPSG:3007
    -> AttributeManager

Bookmark: Delete jpeg
FileDeleter_2
    FileToDelete = $(FME_SHAREDRESOURCE_TEMP)/FME120/@Value(Values.bild_ovanifran.File.Name)

Bookmark: Set status
HTTPCaller_2
    AUTH_METHOD = Web Connection
    AUTH_NAMED_CONNECTION = API User
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://minasidor-api.trollhattan.se:8443/api/callback/WSDL
    TRANSFER_TIMEOUT_LENGTH = 90
    UPLOAD_BODY:
      <?xml version="1.0" encoding="utf-8"?>
      <soap:Envelope xmlns:soap="http://schemas.xmlsoap.org/soap/envelope/">
        <soap:Body>
          <setStatus xmlns="http://www.oeplatform.org/version/1.0/schemas/integration/callback">
            <flowInstanceID>@Value(_case)</flowInstanceID>
            <statusAlias>@Value(_opene.status)</statusAlias>
          </setStatus>
        </soap:Body>
      </soap:Envelope>
    UPLOAD_CONTENT_TYPE = text/xml;charset=UTF-8
    UPLOAD_TYPE = Specify Upload Body
    USE_COOKIES = No
    VERIFY_SSL_CERTIFICATES = Yes
    -> TestFilter_2

Bookmark: Send e-mail
TestFilter_2
    DEFAULT_VALUE = <UNFILTERED>
    PASSED_TEST_GROUP_OUTPUT = FIRST
    TEST_LIST = "BOOL_OP,OR,COMPOSITE_TEST,""""""1"""""",TEST_CLAUSE,TEST Values.mailadress.mailadress ATTRIBUTE_HAS_A_VALUE """,Send email
    Send email -> AttributeCreator_3
AttributeCreator_3
    ATTR_TABLE:
      SET_TO _email.foot
      SET_TO _email.head = <p>
        <h1>
        Fastighetsgränser - Fotografera gränsmarkeringar
        </h1>
        </p>
      SET_TO _email.sender = noreply.minasidor@trollhattan.se
    -> Emailer
Emailer
    BODY:
      <html>
      <body>
      @Value(_email.head)
      @Value(_email.message)
      <br>
      @Value(_email.foot)
      </body>
      </html>
    FROM = @Value(_email.sender)
    SERVICE = Generic SMTP
    SMTP_CONNECTION = HOST;smtp.thn.local;PORT;25;ENCRYPTION;None;TIMEOUT;60;AUTHENTICATION;NO;USERNAME;<Unused>;PASSWORD;<Unused>;FME_CONTROLLER_QUERY_FILE;dependencies/Generic SMTP.fme
    SUBJECT = @Value(_email.subject)
    TO = @Value(Values.mailadress.mailadress)

FME custom transformer FileDeleter
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    SUMMARY -> Output (output)
Output (output)
