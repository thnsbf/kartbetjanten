FME workspace ByggnadsmodelltillCesium_ver2.fmw

Parameters:
- KOORD = EPSG:4326   # Sweref 99 12 00,EPSG:3007%Sweref99 TM,EPSG:3006%WGS84,EPSG:4326 Välj koordinatsystem
- EXPORTBYGGNADER =   # Om du vill ha en byggnadsmodell, välj filformat
- DestDataset_CESIUM3DTILES = $(FME_MF_DIR)ExportByggnadsmodell\staden   # Destination Cesium 3D Tiles Folder
- SourceDataset_MSSQL_SPATIAL_4 = CSM databas   # SQL Server Connection
- SourceDataset_SHAPEFILE_3 = ""T:\AppServer\SBF-EFD\SBF-EFD3\byggnadsmodell\Alingsåker.shp" "T:\AppServer\SBF-EFD\SBF-EFD3\byggnadsmodell\Björndalen.shp" "T:\AppServer\SBF-EFD\SBF-EFD3\byggnadsmodell\Centrala staden.shp" "T:\AppServer\SBF-EFD\SBF-EFD3\byggnadsmodell\Dannebacken.shp" "T:\AppServer\SBF-EFD\SBF-EFD3\byggnadsmodell\Halltorp.shp" "T:\AppServer\SBF-EFD\SBF-EFD3\byggnadsmodell\Halvorstorp.shp" "T:\AppServer\SBF-EFD\SBF-EFD3\byggnadsmodell\Hjortmossen.shp" "T:\AppServer\SBF-EFD\SBF-EFD3\byggnadsmodell\Hjulkvarn.shp" "T:\AppServer\SBF-EFD\SBF-EFD3\byggnadsmodell\Hojum.shp" "T:\AppServer\SBF-EFD\SBF-EFD3\byggnadsmodell\Karlstorp.shp" "T:\AppServer\SBF-EFD\SBF-EFD3\byggnadsmodell\Kronogården.shp" "T:\AppServer\SBF-EFD\SBF-EFD3\byggnadsmodell\Källstorp.shp" "T:\AppServer\SBF-EFD\SBF-EFD3\byggnadsmodell\Lextorp.shp" "T:\AppServer\SBF-EFD\SBF-EFD3\byggnadsmodell\Lärketorpet.shp" "T:\AppServer\SBF-EFD\SBF-EFD3\byggnadsmodell\Norra Björke.shp" "T:\AppServer\SBF-EFD\SBF-EFD3\byggnadsmodell\Sandhem.shp" "T:\AppServer\SBF-EFD\SBF-EFD3\byggnadsmodell\Sjuntorp.shp" "T:\AppServer\SBF-EFD\SBF-EFD3\byggnadsmodell\Skoftebyn.shp" "T:\AppServer\SBF-EFD\SBF-EFD3\byggnadsmodell\Skogshöjden.shp" "T:\AppServer\SBF-EFD\SBF-EFD3\byggnadsmodell\Skogstorpa.shp" "T:\AppServer\SBF-EFD\SBF-EFD3\byggnadsmodell\Stallbacka.shp" "T:\AppServer\SBF-EFD\SBF-EFD3\byggnadsmodell\Stavre.shp" "T:\AppServer\SBF-EFD\SBF-EFD3\byggnadsmodell\Strömslund.shp" "T:\AppServer\SBF-EFD\SBF-EFD3\byggnadsmodell\Sylte.shp" "T:\AppServer\SBF-EFD\SBF-EFD3\byggnadsmodell\Tingvalla.shp" "T:\AppServer\SBF-EFD\SBF-EFD3\byggnadsmodell\Torsred.shp" "T:\AppServer\SBF-EFD\SBF-EFD3\byggnadsmodell\Upphärad.shp" "T:\AppServer\SBF-EFD\SBF-EFD3\byggnadsmodell\utanför tätorterna.shp" "T:\AppServer\SBF-EFD\SBF-EFD3\byggnadsmodell\Velanda.shp" "T:\AppServer\SBF-EFD\SBF-EFD3\byggnadsmodell\Vårvik.shp" "T:\AppServer\SBF-EFD\SBF-EFD3\byggnadsmodell\Väne-Åsaka.shp" "T:\AppServer\SBF-EFD\SBF-EFD3\byggnadsmodell\Åker.shp" "T:\AppServer\SBF-EFD\SBF-EFD3\byggnadsmodell\Överby.shp""   # Source Esri Shapefile(s)
- FEATURE_TYPES =

Readers:
- MSSQL_SPATIAL_3: MSSQL_SPATIAL from $(SourceDataset_MSSQL_SPATIAL_4) in SWEREF-99-12-00
- SHAPEFILE_2: SHAPEFILE from $(SourceDataset_SHAPEFILE_3) in SWEREF-99-12-00

Writers:
- CESIUM3DTILES_1: CESIUM3DTILES to $(DestDataset_CESIUM3DTILES) in EPSG:4326

AFI_FAST_YTA_GML (reader MSSQL_SPATIAL_3)
    attributes: FNR_FR integer, TRAKT varchar(50), BLOCK_ENHET varchar(9), OMRADE integer, FASTIGHET varchar(64), EXTID varchar(64), DEP varchar(10), ANTAL_OMR smallint, SAMJEBET varchar(15), TILLAGG varchar(1), XYFEL numeric(12,6), ZFEL numeric(12,6), UUID char(100)
    -> AttributeRemover
AttributeRemover
    REMOVE_ATTRS = ANTAL_OMR,BLOCK_ENHET,DEP,EXTID,FNR_FR,OMRADE,SAMJEBET,TILLAGG,TRAKT,UUID,XYFEL,ZFEL
    -> Counter
Counter
    CNT_ATTR = fastighet
    DOMAIN = counter
    SCOPE = Global
    START = 0
    -> AreaOnAreaOverlayer [AREA]
Alingsåker (reader SHAPEFILE_2)
    attributes: stadsdel varchar(40), mi_style varchar(48), id_nr number(31,15), uuid varchar(70), areal_ha number(31,15), fill varchar(254), fill-opaci number(31,15), stroke varchar(254), stroke-wid number(20,0), fme_featur varchar(200), Q__counter number(20,0), Q__BuildID varchar(200), BYGGNUMMER varchar(200), EGID_value varchar(200), Q__r varchar(200), Q__g varchar(200), Q__b varchar(200), Q__col varchar(200), B_Part varchar(200), igds_color varchar(200), igds_weigh varchar(200), igds_style varchar(200), igds_class varchar(200), igds_graph varchar(200), EGID_tagse varchar(200), igds_text_ varchar(200), EGID_defau varchar(200), igds_inser varchar(200), TYPE_tagse varchar(200), igds_tex00 varchar(200),
      TYPE varchar(200), EGID varchar(200), igds_ins00 varchar(200), TYPE_tagty varchar(200), TYPE_value varchar(200), EGID_tagty varchar(200), TYPE_defau varchar(200), EGID_name varchar(200), igds_ins01 varchar(200), igds_rotat varchar(200), TYPE_name varchar(200), igds_origi varchar(200), Q__geometr varchar(200), Q__part_nu varchar(200), Q__ID_Vert number(20,0), Q__area number(31,15), Q__clipped varchar(200), Q__orienta varchar(254), Q__xmax number(31,15), Q__xmin number(31,15), Q__ymax number(31,15), Q__ymin number(31,15), Q__zmax number(31,15), Q__zmin number(31,15), Q__SSID number(20,0), Q__SSArea1 number(31,15), Q__New_tes number(20,0), Q__floor_e number(31,15), DGN_LEVEL varchar(200), Q__Build_I number(20,0),
      dist varchar(200), Q__dimensi number(31,15), error varchar(254), snapped varchar(254), fme_reject varchar(254), Q__xmaxSS number(31,15), Q__xminSS number(31,15), Q__ymaxSS number(31,15), Q__yminSS number(31,15), Q__zmaxSS number(31,15), Q__zminSS number(31,15), layer varchar(254), path varchar(254), AREA_DGN varchar(18)
    -> AreaOnAreaOverlayer [AREA]
AreaOnAreaOverlayer
    ACCUM_ATTRS_NAME = Merge Incoming Attributes
    CLEANING_TOLERANCE = Automatic
    CONNECT_Z_MODE = First Wins
    DEAGGREGATE_INPUT = Yes
    OVC_ATTR = _overlaps
    AREA -> CoordinateExtractor
    REMNANTS -> CoordinateExtractor
CoordinateExtractor
    IND = 0
    MODE = Specify Coordinate
    X_ATTR = _x
    Y_ATTR = _y
    Z_ATTR = _z
    -> Tester
Tester
    BOOL_OP = OR
    TEST_CLAUSE = TEST _z ATTRIBUTE_VALUE_NULL ""
    TEST_MODE = TEST
    PASSED -> Inspector_2
    PASSED -> Extruder_2
Inspector_2
Extruder_2 [off]
    DIRECTION = Vertical
    DISTANCE = 0.001
    EXTRUDED -> Aggregator [off]
Aggregator [off]
    ACCUM_ATTRS_NAME = Drop Incoming Attributes
    AGGREGATE_TYPE = Homogeneous Collection (If Possible)
    GROUP_BY = FASTIGHET
    MODE = Geometry - Assemble One Level
    SEP = ,
    AGGREGATE -> Reprojector_8 [off]
Reprojector_8 [off]
    DEST = EPSG:4326
    INTERPOLATION_TYPE_NAME = Nearest Neighbor
    RASTER_CELL_SIZE = Preserve Cells
    RASTER_TOLERANCE = 0.0
    SOURCE = SWEREF-99-12-00
    REPROJECTED -> AppearanceStyler [off]
    REPROJECTED -> AppearanceSetter [GEOMETRY] [off]
AppearanceStyler [off]
    ALPHA = 1
    AMBIENT_COLOR = 0.345098,0.4,0.478431
    DIFFUSE_COLOR = 0.345098,0.4,0.478431
    EMISSIVE_COLOR = 0.345098,0.4,0.478431
    SHININESS = 1
    SPECULAR_COLOR = 0.345098,0.4,0.478431
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP_DISPLAY = Repeat in U and V
    -> AppearanceSetter [APPEARANCE] [off]
AppearanceSetter [off]
    DEF_STORAGE = Create New Definitions
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> Inspector [off]
    -> staden (writer CESIUM3DTILES_1) [off]
staden (writer CESIUM3DTILES_1) [off]
    attributes: FASTIGHET string, fme_appearance_style_name string, fme_appearance_style_diffuse_color string, fme_appearance_style_ambient_color string, fme_appearance_style_specular_color string, fme_appearance_style_emissive_color string, fme_appearance_style_alpha float, fme_appearance_style_shininess float, fme_texture_style_u_offset float, fme_texture_style_v_offset float, fme_texture_style_center_u float, fme_texture_style_center_v float, fme_texture_style_u_scaling_factor float, fme_texture_style_v_scaling_factor float, fme_texture_style_rotation_angle float, fme_texture_style_u_shearing_factor float, fme_texture_style_v_shearing_factor float, fme_texture_style_wrap string, fme_texture_style_border_color string
Inspector [off]
