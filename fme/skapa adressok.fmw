FME workspace skapa adressok.fmw

Parameters:
- SourceDataset_MSSQL_SPATIAL_5 = -   # SQL Server Connection
- DestDataset_JSON = \adresser.json   # Destination JSON (JavaScript Object Notation) File

Readers:
- MSSQL_SPATIAL_1: MSSQL_SPATIAL from $(SourceDataset_MSSQL_SPATIAL_5) in SWEREF-99-12-00

Writers:
- JSON_1: JSON to $(DestDataset_JSON)

Note: Läs in din tabell med adresser
TF_FASTADRESS_GEOFIR_V1 (reader MSSQL_SPATIAL_1)
    attributes: ADRESSPLATS_ID integer, UUID_ADRESSPLATS varchar(36), RNPADRPL smallint, RIDADRPL integer, KOMKOD_ADR char(4), KOMMUNDEL varchar(35), UUID_ADRESSOMRADE varchar(36), BELADRESS varchar(107), BELADRESS2 varchar(135), ADRESSPLATS_TYP varchar(2), ADRPLSTATUS char(1), KOMKOD_FAS char(4), FNR integer, CFDFNR varchar(9), UUID_FASTIGHET varchar(36), FASTIGHET varchar(50), TRAKT varchar(40), FBETNR varchar(9), STATUS char(1), POPNAMN varchar(35), PUNKTTYP_ADR char(1), POSTNR varchar(6), POSTORT varchar(27), LMV_DELETED char(1), XKOORD float, YKOORD float, OMR integer, ADRESSOMRADE varchar(35), ADRESSPLATS varchar(35), ADRESSPLATS_NUMMER integer,
      ADRESSPLATS_LITTERA varchar(10), AVVIKER_FRAN_STANDARD varchar(1), VIEW_VERSION varchar(6)
    -> AttributeManager
Note: Ta bort alla atribut förutom den som innehåller dina belägningsadresser, byt namn på det attributet till "td_adress" och lägg till attributet "td_kommund" och skriv in ditt kommunnamn
AttributeManager
    ATTR_TABLE:
      REMOVE ADRESSPLATS_ID (int32)
      REMOVE UUID_ADRESSPLATS (varchar(36))
      REMOVE RNPADRPL (int16)
      REMOVE RIDADRPL (int32)
      REMOVE KOMKOD_ADR (char(4))
      REMOVE KOMMUNDEL (varchar(35))
      REMOVE UUID_ADRESSOMRADE (varchar(36))
      RENAME_SET_VALUE BELADRESS > td_adress (varchar(107))
      REMOVE BELADRESS2 (varchar(135))
      REMOVE ADRESSPLATS_TYP (varchar(2))
      REMOVE ADRPLSTATUS (char(1))
      REMOVE KOMKOD_FAS (char(4))
      REMOVE FNR (int32)
      REMOVE CFDFNR (varchar(9))
      REMOVE UUID_FASTIGHET (varchar(36))
      REMOVE FASTIGHET (varchar(50))
      REMOVE TRAKT (varchar(40))
      REMOVE FBETNR (varchar(9))
      REMOVE STATUS (char(1))
      REMOVE POPNAMN (varchar(35))
      REMOVE PUNKTTYP_ADR (char(1))
      REMOVE POSTNR (varchar(6))
      REMOVE POSTORT (varchar(27))
      REMOVE LMV_DELETED (char(1))
      REMOVE XKOORD (real64)
      REMOVE YKOORD (real64)
      REMOVE OMR (int32)
      REMOVE ADRESSOMRADE (varchar(35))
      REMOVE ADRESSPLATS (varchar(35))
      REMOVE ADRESSPLATS_NUMMER (int32)
      REMOVE ADRESSPLATS_LITTERA (varchar(10))
      REMOVE AVVIKER_FRAN_STANDARD (varchar(1))
      REMOVE VIEW_VERSION (varchar(6))
      SET_TO td_kommund (buffer) = Trollhättan
    -> StringCaseChanger
Note: Byter till korrekt Case placering
StringCaseChanger
    ATTRCHOICE = All Attributes
    CHANGE_TYPE = Full Title Case
    -> adresser (writer JSON_1)
Note: Spara json filen under mappen json på din server
adresser (writer JSON_1)
    attributes: td_adress string, td_kommund string
